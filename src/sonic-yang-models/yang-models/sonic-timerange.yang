module sonic-timerange {

    yang-version 1.1;

    namespace "http://github.com/sonic-net/sonic-timerange";
    prefix timerange;

    description "TIME_RANGE YANG Module for SONiC OS Used for Scheduled Configuration";

    revision 2024-05-09 {
        description "First Revision";
    }

    container sonic-timerange {

        container TIME_RANGE {

            description "TIME_RANGE part of config_db.json";

            list TIME_RANGE_LIST {
                description "List of time ranges, each identified by unique name";

                key "name";

                leaf name {
                    type string;
                    description "Unique name for the time range";
                }

                leaf start {
                    mandatory true;
                    type string {
                        length "1..255";
                    }
                    description "Start time for time range";
                }

                leaf end {
                    mandatory true;
                    type string {
                        length "1..255";
                    }
                    description "End time for time range";
                }

                leaf start_year {
                    type uint16;
                    description "Indicates what year this time range will begin running";
                }

                leaf end_year {
                    type uint16;
                    description "Indicates what year this time range will end";
                }
            } /* end of list TIME_RANGE_LIST */
            
        } /* end of container TIME_RANGE */
        
    } /* end of top level container */
    
} /* end of module sonic-timerange */
